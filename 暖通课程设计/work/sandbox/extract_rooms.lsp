(setq f (open "D:/CodexWork/??/??????/work/sandbox/room_data.txt" "w"))
(setq ss (ssget "X" (list (cons 0 "TEXT,MTEXT"))))
(if ss
  (progn
    (setq i 0)
    (setq n (sslength ss))
    (while (< i n)
      (setq e (ssname ss i))
      (setq elist (entget e))
      (setq txt (cdr (assoc 1 elist)))
      (setq pos (cdr (assoc 10 elist)))
      (setq lay (cdr (assoc 8 elist)))
      (write-line (strcat txt "|" (rtos (car pos) 2 0) "|" (rtos (cadr pos) 2 0) "|" lay) f)
      (setq i (+ i 1))
    )
  )
)
(close f)
(princ)
